(defun c:15demo1()
	(setvar "cmdecho" 0)
	(princ "选择要更改半径的圆：")
;;;	(setq ss (ssget))
	(setq p1 (getpoint))
	(setq p2 (getcorner p1))
	(if (> (car p1) (car p2))
		(setq ss (ssget "c" p1 p2))
		(setq ss (ssget "w" p1 p2))
		)
	(setq rate (getreal "\n输入更改半径的比例<2>:"))
	(if (= rate nil) (setq rate 2))
	(setq n 0)
	(repeat (sslength ss)
		(setq ent (ssname ss n))
		(setq ent_data (entget ent))
		(setq ent_type (cdr (assoc 0 ent_data)))
		(if (= ent_type "CIRCLE")
			(progn
				(setq r (cdr (assoc 40 ent_data)))
				(setq r (* r rate))
				(setq ent_data (subst (cons 40 r) (assoc 40 ent_data) ent_data))
				(entmod ent_data)
				)
			)
		(setq n (+ n 1))
	)

)
